module vxlan-srv {

  namespace "http://example.com/vxlan-srv";
  prefix vxlan-srv;

  import ietf-inet-types {
    prefix inet;
  }
  import tailf-common {
    prefix tailf;
  }
  import tailf-ncs {
    prefix ncs;
  }

  description
    "Bla bla...";

  revision 2016-01-01 {
    description
      "Initial revision.";
  }

  list vxlan-srv {
    description "This is an RFS skeleton service";

    key name;
    leaf name {
      tailf:info "Unique service id";
      tailf:cli-allow-range;
      type string;
    }

    uses ncs:service-data;
    ncs:servicepoint vxlan-srv-servicepoint;


    list l2_service {
      key name;
      leaf name{
        type string;
      }
      list devices{
        key name;
        leaf name{
          type string;
        }
        leaf vlan_id{
          type string;
        } 
        leaf vni_id{
          type string;
        }
        leaf nve_id{
          type string;
        } 
        leaf nve_mgroup{
          type string;
        }   
        leaf vrf {
          type string;
        }
        leaf ip {
          type string;
        }
        leaf gp_mcast_mac {
          type string;
        }
        leaf gp_mcast_group {
          type string;
        }
        leaf ip_anycast_address {
          type string;
        }
      }
    }

    list l3_service { 
      key name;
      leaf name{
        type string;
      }
      list devices{
        key name;
        leaf name{
          type string;
        }
        leaf vlan_id{
          type string;
        } 
        leaf vni_id{
          type string;
        }
        leaf nve_id{
          type string;
        } 
        leaf vrf {
          type string;
        }
      }
    }
    
    container bgp{
      container spines{
        container devices{
          list device{
            key name;
            leaf name{
              type string;
            }
            leaf dev{
              type string;
            }
            leaf id{
              type string;
            }
          }
        }
        leaf asn{
          type string;
        }
        leaf-list neighbors{
          type string;
        }
      }

      container leafs{
        container devices{
          list device{
            key name;
            leaf name{
              type string;
            }
            leaf dev{
              type string;
            }
            leaf id{
              type string;
            }
          }
        }
        leaf asn{
          type string;
        }
        leaf-list neighbors{
          type string;
        }
      }

    }


    list interfaces {
      key name;
      leaf name {
        type string;
      } 
      leaf dev{
        type string;
      }
      list interface {
        key ifn;
        leaf ifn{
          type string;
        }
        leaf vlan_id {
          type string;
        }
      }
    }  
  }
}
